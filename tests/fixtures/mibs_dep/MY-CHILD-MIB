MY-CHILD-MIB DEFINITIONS ::= BEGIN

IMPORTS
    MODULE-IDENTITY, OBJECT-TYPE, Integer32
        FROM SNMPv2-SMI
    myBaseMIB
        FROM MY-BASE-MIB;

myChildMIB MODULE-IDENTITY
    LAST-UPDATED "200001010000Z"
    ORGANIZATION "Child"
    CONTACT-INFO "Child"
    DESCRIPTION "Child MIB depending on MY-BASE-MIB"
    ::= { myBaseMIB 1 }

childObject OBJECT-TYPE
    SYNTAX      Integer32
    MAX-ACCESS  read-only
    STATUS      current
    DESCRIPTION "Child object"
    ::= { myChildMIB 1 }

END
